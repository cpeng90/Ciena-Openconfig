module openconfig-ospf {

  yang-version "1";

  // namespace
  namespace "http://openconfig.net/yang/ospf";

  prefix "oc-ospf";

  // import some basic types
  //import ietf-inet-types { prefix inet; }
  import openconfig-extensions { prefix "oc-ext"; }

  // Include submodules
  // Global:  All global context groupings;
  include openconfig-ospf-global;
  include openconfig-ospfv2-global.yang;
  // Area:    Config/opstate for an area
  include openconfig-ospf-area;
  // Area Interface:  Config/opstate for an Interface
  include openconfig-ospf-area-interface;
  include openconfig-ospfv2-area-interface;
  include openconfig-ospfv3-area-interface;
  // LSDB: Operational state model covering the LSDB
  include openconfig-ospf-lsdb;
  // Common:  Content included in >1 context
  include openconfig-ospf-common;

  // meta
  organization "OpenConfig working group";

  contact
    "OpenConfig working group
    www.openconfig.net";

  description
    "An OpenConfig model for Open Shortest Path First (OSPF)
    version 2";

  oc-ext:openconfig-version "0.3.0";

  revision "2019-07-30" {
    description
      "Add support for OSPFv3.";
    reference "0.3.0";
  }

  revision "2019-07-09" {
    description
      "Normalise all timeticks64 to be expressed in nanoseconds.";
    reference "0.2.0";
  }

  revision "2018-11-21" {
    description
      "Add OpenConfig module metadata extensions.";
    reference "0.1.3";
  }

  revision "2018-06-05" {
    description
      "Bug fixes in when statements in lsdb";
    reference "0.1.2";
  }

  revision "2017-08-24" {
    description
      "Minor formatting fixes.";
    reference "0.1.1";
  }

  revision "2017-02-28"{
    description
      "Initial public release of OSPFv2";
    reference "0.1.0";
  }

  revision "2016-06-24" {
    description
      "Initial revision";
    reference "0.0.1";
  }

  // OpenConfig specific extensions for module metadata.
  oc-ext:regexp-posix;
  oc-ext:catalog-organization "openconfig";
  oc-ext:origin "openconfig";

  grouping ospfv2-top {
    description
      "Top-level OSPFv2 configuration and operational state";

    container ospf {
      description
        "Top-level configuration and operational state for
        Open Shortest Path First (OSPF) v2";

      uses ospf-global-structural;

      container areas {
        description
          "Configuration and operational state relating to an
	  OSPFv2 area.";

        list area {
          key "identifier";

          description
            "The OSPFv2 areas within which the local system exists";

          leaf identifier {
            type leafref {
              path "../config/identifier";
            }
            description
              "A reference to the identifier for the area.";
          }

          uses ospf-area-structure;
        }
      }
    }
  }

  grouping ospfv3-top {
    description
      "Top-level OSPFv3 configuration and operational state";

    container ospfv3 {
      description
        "Top-level configuration and operational state for
        Open Shortest Path First (OSPF) v3";

      uses ospf-global-structural;

      container areas {
        description
          "Configuration and operational state relating to an
          OSPFv3 area.";

        list area {
          key "identifier";

          description
            "The OSPFv3 areas within which the local system exists";

          leaf identifier {
            type leafref {
              path "../config/identifier";
            }
            description
              "A reference to the identifier for the area.";
          }

          uses ospf-area-structure;
        }
      }
    }
  }
}
